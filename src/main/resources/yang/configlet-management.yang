submodule configlet-management {
    yang-version 1;
    belongs-to "iq-common-data-model" {
        prefix "iq-cdm";
    }
    // import ietf-inet-types { prefix "inet"; }
    // import ietf-yang-types { prefix "yang"; }
    import iq-ifmap-types { prefix "ifmap"; }
    contact "JUNOS Space <shinma@juniper.net>";
    organization "Juniper Networks";
    description "YANG definition for the configlet-management module";
    revision "2015-02-05" {
        description "Initial revision";
    }

    list configlet {
        description "Configlet";
        uses ifmap:Identity;
        key uuid;
    }
}
