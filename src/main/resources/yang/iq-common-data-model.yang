module iq-common-data-model {
    yang-version 1;
    namespace "http://www.juniper.net/ns/vnc";
    prefix "iq-cdm";

    include configlet-management;
    include configuration-file-management;
    include device-management;
    include image-management;
    include script-management;
    include template-management;

    contact "JUNOS Space <jspace@juniper.net>";

    organization "Juniper Networks";

    description "YANG version for the device-management";

    revision "2015-02-05" {
        description "Initial revision";
    }
}
